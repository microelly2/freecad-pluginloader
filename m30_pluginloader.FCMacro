import FreeCAD,PySide,os,FreeCADGui,time
from PySide import QtCore, QtGui, QtSvg
from PySide.QtGui import * 

def say(s):
	FreeCAD.Console.PrintMessage(str(s)+"\n")

def starty(*args):
	import pluginloader
	reload(pluginloader)
	plulo=pluginloader.PluginLoader()
	plulo.setParams()
	plulo.getParams()
	plulo.starthide()

t=FreeCADGui.getMainWindow()
t.workbenchActivated.connect(starty)
Gui.activateWorkbench("DraftWorkbench")
